# MapAppV01

# Specification: Requirements Document
- ReqIF.Description: Requirements Document

## REQ-3
A mobile device MAY have a map application.
- isMandatory: false

### REQ-4
A map application SHALL use and show existing cloud-based maps in a mash-up manner.
- isMandatory: true

### REQ-5
A map application MAY provide ability to store or cache maps locally to device. Locally stored maps potentially save networking costs especially when the map application is being used abroad. Locally stored maps enable the map application to work under bad network coverage.
- isMandatory: false

### REQ-6
A map application MAY provide GPS positioning. GPS positioning shows the current location on the map
- isMandatory: false

### REQ-7
A map application MAY provide routing and navigation functionality that provide the user with guidance.
- isMandatory: false
- Requires -> REQ-6
- Requires -> REQ-5
